# Beispiel

## #1: Schraubfähigkeit (Functional)
Drehmoment (Nm): Die Fähigkeit, eine bestimmte Kraft zum Eindrehen oder Lösen von Schrauben bereitzustellen. (Anforderung: Einstellbares Drehmoment zur Anpassung an unterschiedliche Schraubengrößen und Materialien).
Drehzahl (U/min): Die Geschwindigkeit, mit der sich die Schraube dreht. (Anforderung: Mehrere Gänge oder stufenlose Drehzahlregelung für schnelle und präzise Arbeiten).
Rechts-/Linkslauf: Muss Schrauben sowohl ein- als auch ausdrehen können.

## #2: Bohrfähigkeit (Functional)
Hohe Drehzahl: Notwendig für effizientes Bohren in verschiedenen Materialien (Holz, Metall, Kunststoff).
Bohrfutter-Spannweite: Muss gängige Bohrer- und Bitgrößen aufnehmen können (häufig bis 10 mm oder 13 mm).
Schlagfunktion (bei Akku-Schlagbohrschraubern): Die Fähigkeit, in härtere Materialien wie Mauerwerk oder Beton zu bohren.

## #3: Energieversorgung und Ausdauer (Functional)
Akkuspannung (Volt): Bestimmt die maximale Kraft/Leistung des Schraubers (z.B. 12V für leichte Arbeiten, 18V für anspruchsvolle Aufgaben).
Akkukapazität (Ah - Amperestunden): Bestimmt die Laufzeit pro Ladung (Anforderung: Ausreichende Kapazität für geplante Arbeiten).
Schnellladefähigkeit: Kurze Ladezeiten des Akkus für unterbrechungsfreies Arbeiten.

## #4: Handhabung und Ergonomie (Functional)
Gewicht und Balance: Geringes Gewicht für ermüdungsfreies Arbeiten, besonders bei Überkopfarbeiten.
Kompakte Bauform: Für das Arbeiten an schwer zugänglichen Stellen.

## #5: Zusatzfunktionen (Functional)
Arbeitslicht (LED): Beleuchtung des Arbeitsbereichs.
Bürstenloser Motor (Brushless): Höhere Effizienz, längere Lebensdauer und kompaktere Bauweise.
