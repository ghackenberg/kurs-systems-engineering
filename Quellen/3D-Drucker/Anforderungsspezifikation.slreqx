# Anforderungsspezifikation

## #1: Leichte Austauschbarkeit der Düse (Informational)
Düse kann kaputt gehen, muss regelmäßig ausgetauscht werden
Austausch ohne Schlung sollte möglich sein
- Rationale: Kein aufwändiger Kundendienst notwendig, spart Geld
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
## #2: Kunststoff schmelzen (Functional)

## #3: Sicherheitsanforderungen (Container)

### #4: Gehäuse (Informational)

### #5: Prozess nur aktiv, wenn Schutztür geschlossen (Functional)
